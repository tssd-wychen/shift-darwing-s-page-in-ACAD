(defun c:PGB_pagebase()
  (vl-load-com)
  (defun FIND_MULTI_PTY (en_pty key / );输入为联合属性列表 和 键值,返回值为带相应键值的列表,测试量en_pty
    (setq pty_dem (vl-remove-if-not '(lambda (x) (= (car x) key)) en_pty))
  )
  (defun SS2NDFTLR(ss filter)
    (vl-cmdf "select" ss "")
    (ssget "P" filter)
  )
  (defun SS2ENLST(ss )
    (setq enlst nil)
    (if ss
      (repeat (sslength ss)
	(setq enlst (cons (ssname basess (length enlst)) enlst))
      )
      (progn
	(alert "no entity in this selected set")
      )
    )
    enlst
  )
  (defun ESTI_LIN_PTS(linptpr ptlist / ps pf p_x norm ptlist_n pt2dlist_n ps2d distlst mindist i_mind)
    (setq norm (mapcar '- (nth 1 linptpr) (nth 0 linptpr)))
    (setq ps (trans (nth 0 linptpr) 1 norm));point start line
    (setq pf (trans (nth 1 linptpr) 1 norm));point finish line
    (setq p_x -1)
    (setq ptlist_n (mapcar '(lambda(ptx)(setq p_x (1+ p_x))(cons p_x (trans ptx 1 norm))) ptlist))
    (setq ptlist_n (vl-remove-if-not
		     '(lambda(ptx)
			(and (> (caddr pf) (cadddr ptx))
			     (< (caddr ps) (cadddr ptx))
			     )
			)
		     ptlist_n)
	  )
    (if ptlist_n
      (progn
	(setq pt2dlist_n (mapcar '(lambda(ptx)(list (cadr ptx)(caddr ptx))) ptlist_n))
	(setq ps2d (list (car ps)(cadr ps)))
	(setq distlst (mapcar '(lambda(ptx)(distance ps2d ptx)) pt2dlist_n))
	(setq mindist (apply 'min distlst))
	(setq i_mind (1- (length (member mindist (reverse distlst)))))
	(setq i_mind (car (nth i_mind ptlist_n)))
	(setq ptout (list mindist (nth i_mind ptlist)))
      )
      (setq ptout nil)
    )
  )
  (defun SELENASBASE();select entity as base the frame
    (setq basefilter '((8 . "PRINT,WAKU")); drawing base
	  pgffilter '((0 . "LWPOLYLINE") (8 . "PRINT")); drawing frame
	  pgnfilter '((0 . "TEXT") (8 . "PRINT")); drawing page no
	  pgpfilter '((0 . "Line") (8 . "WAKU"))); drawing base point
    (prompt "select the print base frame")
    (setq basess (ssget basefilter))
    (mapcar '(lambda(x y)(set x (SS2NDFTLR basess y)))
	    (list 'pgfss 'pgnss 'pgpss) (list pgffilter pgnfilter pgpfilter))
    (mapcar '(lambda(x y)(set x (SS2ENLST y)))
	    (list 'pgfenlst 'pgnenlst 'pgpenlst) (list pgfss pgnss pgpss))
    (setq pgplst nil)
    (foreach pgpen pgpenlst
      (setq pgppty (entget pgpen))
      (setq ptlst (mapcar '(lambda(x)(trans (cdr (assoc x pgppty)) (cdr (assoc -1 pgppty)) 1)) '(10 11)))
      (setq seta (apply 'angle ptlst))
      (if (> seta pi)
        (mapcar 'set (list 'seta 'bi) (list (* (- seta pt) (/ 180 pi)) 10))
	(mapcar 'set (list 'seta 'bi) (list (* seta (/ 180 pi)) 11))
      )
      (if (> seta 5)
	(setq pgplst (cons (cdr (assoc bi pgppty)) pgplst))
      )
    )
    (list pgfenlst pgnenlst pgplst)
  )
  (defun CONSPGNO(basenlst pgbenlst / pgbbdpt1 pgbbdpt2 pgbbdpt pgbpty pgbd pgbdsel upppgbd pgbbptlst fitpgbbpt fitpgben pgnotxt)
    (foreach pgbeni pgbenlst; page no txt center point
      (setq pgbobj (vlax-ename->vla-object pgbeni))
      (vla-getboundingbox pgbobj 'pgbbdpt1 'pgbbdpt2)
      (setq pgbbdpt1 (vlax-safearray->list pgbbdpt1))
      (setq pgbbdpt2 (vlax-safearray->list pgbbdpt2))
      (setq pgbbdpt (mapcar '(lambda(lpi)(/ lpi 2)) (mapcar '+ pgbbdpt1 pgbbdpt2)));lp point list
      (setq pgbenlst (subst (cons pgbbdpt pgbeni) pgbeni pgbenlst));tmkbptlst: text mark base point list
    )
    (foreach basen basenlst
      (setq pgbpty (entget basen))
      (setq pgbd (mapcar 'cdr (FIND_MULTI_PTY pgbpty 10)));page bound
      (setq pgbdsel (mapcar '(lambda(ptx)(trans ptx basen 1)) pgbd))
      (setq pgbdsel (vl-sort pgbdsel '(lambda(p1 p2)(> (cadr p1)(cadr p2)))))
      (setq upppgbd (list (car pgbdsel)(cadr pgbdsel)))
      (setq pgbbptlst (mapcar 'car pgbenlst))
      (setq fitpgbbpt (ESTI_LIN_PTS upppgbd pgbbptlst))
      (setq fitpgbbpt (cadr fitpgbbpt))
      (setq fitpgben (cdr (assoc fitpgbbpt pgbenlst)))
      (if fitpgben
	(progn
          (setq pgnotxt (cdr (assoc 1 (entget fitpgben))))
	  (setq pgnotxt (cddr (vl-remove 32 (vl-string->list pgnotxt))))
	  (setq pgnotxt (atoi (vl-list->string pgnotxt)))
        )
	(setq pgno -1)
      )
      (setq basenlst (subst (cons pgnotxt basen) basen basenlst))
    )
    basenlst
  )
  (defun CONSBPT(basenlst pgplst)
    (setq pgfenlst (mapcar 'cdr basenlst))
    (foreach pgfen pgfenlst
      (setq pgfpty (entget pgfen))
      (setq pgbd (mapcar 'cdr (FIND_MULTI_PTY pgfpty 10)));page bound
      (setq pgbdsel (mapcar '(lambda(ptx)(trans ptx pgfen 1)) pgbd))
      (setq pgbdsel (vl-sort pgbdsel '(lambda(p1 p2)(< (car p1)(car p2)))))
      (setq lftpgbd (list (car pgbdsel)(cadr pgbdsel)))
      (setq fitpgbpt (ESTI_LIN_PTS lftpgbd pgplst))
      (setq fitpgbpt (cadr fitpgbpt))
      (setq newspgfen (append (list pgfen) (list fitpgbpt)))
      (setq pgfenlst (subst newspgfen pgfen pgfenlst))
    )
    (setq basenlst (mapcar '(lambda(x y)(cons (car x) y)) basenlst pgfenlst))
  )
  ;;;;;;;;;;;;;;;;;;;;;;;;;;;;;;;;;;;;;;;;;;;;;;;;;;;;;;;;;;;;;;;;;;;;;;;;;;
  (setq baseenlist (SELENASBASE))
  (mapcar 'set (list 'pgfrenlist 'pgnoenlist 'pgbptlist) baseenlist)
  (setq pgfrenlist (CONSPGNO pgfrenlist pgnoenlist))
  (setq baseenlist (CONSBPT pgfrenlist pgbptlist))
  baseenlist
  (setq blankpg (assoc -1 baseenlist))
  (setq baseenlist (vl-remove blankpg baseenlist))
  (setq mxpgno (apply 'max (mapcar 'car baseenlist)))
  (setq mnpgno (apply 'min (mapcar 'car baseenlist)))
  (setq countpg mxpgno)
  (setq pgctfilter '((-4 . "<not") (8 . "WAKU,Page No,PRINT") (-4 . "not>")))
  (while (>= countpg mnpgno)
    (if (= countpg mxpgno)
      (progn
        (setq pgframe (cadr (assoc countpg baseenlist)))
        (setq pgframepty (entget pgframe))
        (setq pgfptlst (FIND_MULTI_PTY pgframepty 10))
        (setq pgfptlst (mapcar '(lambda(ptx)(trans ptx pgframe 1)) pgfptlst))
        (setq pgctss (ssget "WP" pgfptlst pgctfilter))
        (setq stbpt (car (reverse (assoc countpg baseenlist)))
  	      spbpt (car (reverse blankpg))
        )
        (command "move" pgctss stbpt spbpt "")
      )
    )
    (setq pgframe (cadr (assoc countpg baseenlist)))
    (setq pgframepty (entget pgframe))
    (setq pgfptlst (FIND_MULTI_PTY pgframepty 10))
    (setq pgfptlst (mapcar '(lambda(ptx)(trans ptx pgframe 1)) pgfptlst))
    (setq pgctss (ssget "WP" pgfptlst pgctfilter))
    (setq stbpt (car (reverse (assoc countpg baseenlist)))
  	      spbpt (car (reverse (assoc (1+ countpg) baseenlist)))
    )
    (command "move" pgctss stbpt spbpt "")
  )
)

(defun selstpg()
    (setq notselected T)
    (while notselected
      (setq stpgen (car (entsel "select the page base you want to del or vacate\nNOTICE:the page no of the page you selected should be check!")))
      (if stpgen
	(progn
	  (setq stpgpty (entget stpgen))
	  (if (and (member '(8 . "PRINT") stpgpty) (member '(0 . "LWPOLYLINE") stpgpty))
	    (setq notselected nil)
	    (alert "no such page base selected")
	  )
	)
	(alert "no such page base selected")
      )
    )
    (list stpgen)
  )

(defun cross()
  (entsel))
